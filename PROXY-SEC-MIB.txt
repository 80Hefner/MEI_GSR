PROXY-SEC-MIB DEFINITIONS ::= BEGIN

IMPORTS
	private
		FROM SNMPv2-SMI;

proxyMIB MODULE-IDENTITY
	LAST-UPDATED "202208290835Z"	-- Aug 29, 2022, 8:35:00 AM
	ORGANIZATION ""
	CONTACT-INFO
		""
	DESCRIPTION
		""
	REVISION "202208290835Z"	-- Aug 29, 2022, 8:35:00 AM
	DESCRIPTION
		"Initial version."
	-- 1.3.6.1.4.101
	::= { private 101 }


-- Scalars and Tables
--

proxyObjects OBJECT IDENTIFIER 
	-- 1.3.6.1.4.101.1
	::= { proxyMIB 1 }

proxyOperationsTable OBJECT-TYPE
	SYNTAX  SEQUENCE OF ProxyOperationEntry
	MAX-ACCESS not-accessible
	STATUS  current
	DESCRIPTION
		"Esta tabela é usada para gerir operações requisitadas por um gestor"
	-- 1.3.6.1.4.101.1.1
	::= { proxyObjects 1 }


proxyOperationEntry OBJECT-TYPE
	SYNTAX  ProxyOperationEntry
	MAX-ACCESS not-accessible
	STATUS  current
	DESCRIPTION
		"Entrada na tabela de operações do proxy"
	INDEX {
		idOper }
	-- 1.3.6.1.4.101.1.1.1
	::= { proxyOperationsTable 1 }


ProxyOperationEntry ::= SEQUENCE {

	idOper        Unsigned32,
	typeOper      Unsigned32,
	idSource      OCTET STRING,
	idDestination OCTET STRING,
	oidArg        OBJECT IDENTIFIER,
	valueArg      Opaque,
	typeArg       Unsigned32,
	sizeArg       Unsigned32 }


idOper OBJECT-TYPE
	SYNTAX  Unsigned32
	MAX-ACCESS read-only
	STATUS  current
	DESCRIPTION
		"Identificador da operação recebida pelo agente proxy. Serve como chave da tabela"
	-- 1.3.6.1.4.101.1.1.1.1
	::= { proxyOperationEntry 1 }


typeOper OBJECT-TYPE
	SYNTAX  Unsigned32
	MAX-ACCESS read-only
	STATUS  current
	DESCRIPTION
		"Identificador do tipo de operação a ser executada"
	-- 1.3.6.1.4.101.1.1.1.2
	::= { proxyOperationEntry 2 }


idSource OBJECT-TYPE
	SYNTAX  OCTET STRING
	MAX-ACCESS read-only
	STATUS  current
	DESCRIPTION
		"Alias identificativo da fonte do pedido (gestor)"
	-- 1.3.6.1.4.101.1.1.1.3
	::= { proxyOperationEntry 3 }


idDestination OBJECT-TYPE
	SYNTAX  OCTET STRING
	MAX-ACCESS read-only
	STATUS  current
	DESCRIPTION
		"Alias identificativo do destino do pedido e onde a operação será executada (agente SNPv2c)"
	-- 1.3.6.1.4.101.1.1.1.4
	::= { proxyOperationEntry 4 }


oidArg OBJECT-TYPE
	SYNTAX  OBJECT IDENTIFIER
	MAX-ACCESS read-only
	STATUS  current
	DESCRIPTION
		"Object Identifier do objecto da MIB que é argumento da operação"
	-- 1.3.6.1.4.101.1.1.1.5
	::= { proxyOperationEntry 5 }


valueArg OBJECT-TYPE
	SYNTAX  Opaque
	MAX-ACCESS read-write
	STATUS  current
	DESCRIPTION
		"Resultado da operação executada no agente SNMPv2c.
		Esta entrada da tabela é do tipo Opaque e será necessário aceder à coluna 'typeArg'
		para saber o seu tipo e à 'sizeArg' para saber o seu tamanho"
	-- 1.3.6.1.4.101.1.1.1.6
	::= { proxyOperationEntry 6 }


typeArg OBJECT-TYPE
	SYNTAX  Unsigned32
	MAX-ACCESS read-write
	STATUS  current
	DESCRIPTION
		"Identificador sequencial do tipo de dados de 'valueArg'"
	DEFVAL { 0 }
	-- 1.3.6.1.4.101.1.1.1.7
	::= { proxyOperationEntry 7 }


sizeArg OBJECT-TYPE
	SYNTAX  Unsigned32
	MAX-ACCESS read-write
	STATUS  current
	DESCRIPTION
		"Tamanho em bytes de 'valueArg'.
		Enquanto o valor da operação não for retornado, esta entrada deverá ser igual a zero"
	DEFVAL { 0 }
	-- 1.3.6.1.4.101.1.1.1.8
	::= { proxyOperationEntry 8 }


proxyAgentsTable OBJECT-TYPE
	SYNTAX  SEQUENCE OF ProxyAgentsTableEntry
	MAX-ACCESS not-accessible
	STATUS  current
	DESCRIPTION
		"Esta tabela é usada para guardar as informações dos agentes remotos"
	-- 1.3.6.1.4.101.1.2
	::= { proxyObjects 2 }


proxyAgentsTableEntry OBJECT-TYPE
	SYNTAX  ProxyAgentsTableEntry
	MAX-ACCESS not-accessible
	STATUS  current
	DESCRIPTION
		"Entrada na tabela dos agentes remotos do proxy"
	INDEX {
		agentAlias }
	-- 1.3.6.1.4.101.1.2.1
	::= { proxyAgentsTable 1 }


ProxyAgentsTableEntry ::= SEQUENCE {

	agentAlias   OCTET STRING,
	agentAddress OCTET STRING,
	agentCS      OCTET STRING }


agentAlias OBJECT-TYPE
	SYNTAX  OCTET STRING
	MAX-ACCESS read-only
	STATUS  current
	DESCRIPTION
		"Alias identificativo do agente"
	-- 1.3.6.1.4.101.1.2.1.1
	::= { proxyAgentsTableEntry 1 }


agentAddress OBJECT-TYPE
	SYNTAX  OCTET STRING
	MAX-ACCESS read-write
	STATUS  current
	DESCRIPTION
		"Endereço IP + porta UDP associados ao agente"
	-- 1.3.6.1.4.101.1.2.1.2
	::= { proxyAgentsTableEntry 2 }


agentCS OBJECT-TYPE
	SYNTAX  OCTET STRING
	MAX-ACCESS read-only
	STATUS  current
	DESCRIPTION
		"Community string associada ao agente"
	-- 1.3.6.1.4.101.1.2.1.3
	::= { proxyAgentsTableEntry 3 }


proxyManagersTable OBJECT-TYPE
	SYNTAX  SEQUENCE OF ProxyManagersTableEntry
	MAX-ACCESS not-accessible
	STATUS  current
	DESCRIPTION
		"Esta tabela é usada para guardar as informações dos gestores"
	-- 1.3.6.1.4.101.1.3
	::= { proxyObjects 3 }


proxyManagersTableEntry OBJECT-TYPE
	SYNTAX  ProxyManagersTableEntry
	MAX-ACCESS not-accessible
	STATUS  current
	DESCRIPTION
		"Entrada na tabela dos gestores do proxy"
	INDEX {
		managerAlias }
	-- 1.3.6.1.4.101.1.3.1
	::= { proxyManagersTable 1 }


ProxyManagersTableEntry ::= SEQUENCE {

	managerAlias  OCTET STRING,
	managerAddres OCTET STRING,
	managerCS     OCTET STRING }


managerAlias OBJECT-TYPE
	SYNTAX  OCTET STRING
	MAX-ACCESS read-only
	STATUS  current
	DESCRIPTION
		"Alias identificativo do gestor"
	-- 1.3.6.1.4.101.1.3.1.1
	::= { proxyManagersTableEntry 1 }


managerAddres OBJECT-TYPE
	SYNTAX  OCTET STRING
	MAX-ACCESS read-write
	STATUS  current
	DESCRIPTION
		"Endereço IP + porta UDP associados ao gestor"
	-- 1.3.6.1.4.101.1.3.1.2
	::= { proxyManagersTableEntry 2 }


managerCS OBJECT-TYPE
	SYNTAX  OCTET STRING
	MAX-ACCESS read-only
	STATUS  current
	DESCRIPTION
		"Community string associada ao gestor"
	-- 1.3.6.1.4.101.1.3.1.3
	::= { proxyManagersTableEntry 3 }


-- Notification Types
--

proxyEvents OBJECT IDENTIFIER 
	-- 1.3.6.1.4.101.2
	::= { proxyMIB 2 }

-- Conformance
--

proxyConf OBJECT IDENTIFIER 
	-- 1.3.6.1.4.101.3
	::= { proxyMIB 3 }

-- Groups
--

proxyGroups OBJECT IDENTIFIER 
	-- 1.3.6.1.4.101.3.1
	::= { proxyConf 1 }

-- Compliances
--

proxyCompliances OBJECT IDENTIFIER 
	-- 1.3.6.1.4.101.3.2
	::= { proxyConf 2 }

proxyBasicGroup OBJECT-GROUP
	OBJECTS {
		typeOper,
		idSource,
		idDestination,
		oidArg,
		valueArg,
		typeArg,
		sizeArg,
		idOper,
		agentAddress,
		agentCS,
		agentAlias,
		managerAddres,
		managerCS,
		managerAlias }
	STATUS  current
	DESCRIPTION
		"Basic objects."
	-- 1.3.6.1.4.101.3.1.1
	::= { proxyGroups 1 }

proxyBasicEvents NOTIFICATION-GROUP
	NOTIFICATIONS {
	}
	STATUS  current
	DESCRIPTION
		"Basic notifications."
	-- 1.3.6.1.4.101.3.1.2
	::= { proxyGroups 2 }

END
